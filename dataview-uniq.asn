TASTE-Dataview DEFINITIONS ::=


BEGIN

MyChoice ::= CHOICE {
    a CHOICE {
        b CHOICE {
            c BOOLEAN,
            d BOOLEAN
        },
        e BOOLEAN
    },
    f BOOLEAN
}

Some-Thing ::= MyInteger

MyInteger   ::= INTEGER (0..255)


My-OctStr    ::= OCTET STRING (SIZE (0..20))

SeqOf ::= SEQUENCE (SIZE(0..100)) OF MyInteger

Weight ::= INTEGER(0..2000)
BoolSensor ::= BOOLEAN

StageTy ::= INTEGER (0..7)
StageArrayTy ::= SEQUENCE (SIZE(8)) OF Weight

SeqBool ::= SEQUENCE(SIZE(1..5)) OF BOOLEAN

default-seqof SeqOf ::= {4,7,9}
default-str My-OctStr ::= 'DEADBEEF'H


END
